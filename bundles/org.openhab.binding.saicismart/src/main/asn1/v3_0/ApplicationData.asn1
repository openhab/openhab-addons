ApplicationDataModule

DEFINITIONS
AUTOMATIC TAGS ::= 
BEGIN
OTA_ChrgMangDataResp ::= SEQUENCE
{
  bmsReserCtrlDspCmd INTEGER(0..255),
  bmsReserStHourDspCmd INTEGER(0..255),
  bmsReserStMintueDspCmd INTEGER(0..255),
  bmsReserSpHourDspCmd INTEGER(0..255),
  bmsReserSpMintueDspCmd INTEGER(0..255),
  bmsOnBdChrgTrgtSOCDspCmd INTEGER(0..255),
  bmsEstdElecRng INTEGER(0..65535),
  bmsAltngChrgCrntDspCmd INTEGER(0..255),
  bmsChrgCtrlDspCmd INTEGER(0..255),
  chrgngRmnngTime INTEGER(0..65535),
  chrgngRmnngTimeV INTEGER(0..255),
  bmsChrgOtptCrntReq INTEGER(0..65535),
  bmsChrgOtptCrntReqV INTEGER(0..255) OPTIONAL,
  bmsPackCrnt INTEGER(0..65535),
  bmsPackCrntV INTEGER(0..255) OPTIONAL,
  bmsPackVol INTEGER(0..65535),
  bmsPackSOCDsp INTEGER(0..65535),
  bmsChrgSts INTEGER(0..255),
  bmsChrgSpRsn INTEGER(0..255),
  clstrElecRngToEPT INTEGER(0..65535),
  bmsPTCHeatReqDspCmd INTEGER(0..255),
  bmsPTCHeatResp INTEGER(0..255) OPTIONAL,
  ccuEleccLckCtrlDspCmd INTEGER(0..255) OPTIONAL,
  bmsPTCHeatSpRsn INTEGER(0..255) OPTIONAL,
  bmsDsChrgSpRsn INTEGER(0..255) OPTIONAL,
  disChrgngRmnngTime INTEGER(0..65535) OPTIONAL,
  disChrgngRmnngTimeV INTEGER(0..255) OPTIONAL,
  imcuVehElecRng INTEGER(0..65535) OPTIONAL,
  imcuVehElecRngV INTEGER(0..255) OPTIONAL,
  imcuChrgngEstdElecRng INTEGER(0..65535) OPTIONAL,
  imcuChrgngEstdElecRngV INTEGER(0..255) OPTIONAL,
  imcuDschrgngEstdElecRng INTEGER(0..65535) OPTIONAL,
  imcuDschrgngEstdElecRngV INTEGER(0..255) OPTIONAL,
  chrgngSpdngTime INTEGER(0..65535) OPTIONAL,
  chrgngSpdngTimeV INTEGER(0..255) OPTIONAL,
  chrgngAddedElecRng INTEGER(0..65535) OPTIONAL,
  chrgngAddedElecRngV INTEGER(0..255) OPTIONAL,
  onBdChrgrAltrCrntInptCrnt INTEGER(0..255) OPTIONAL,
  onBdChrgrAltrCrntInptVol INTEGER(0..255) OPTIONAL,
  ccuOnbdChrgrPlugOn INTEGER(0..255) OPTIONAL,
  ccuOffBdChrgrPlugOn INTEGER(0..255) OPTIONAL,
  chrgngDoorPosSts INTEGER(0..255) OPTIONAL,
  chrgngDoorOpenCnd INTEGER(0..255) OPTIONAL,
  chargeStatus RvsChargingStatus(1),
  bmsAdpPubChrgSttnDspCmd INTEGER(0..255)
}
RvsChargingStatus ::= SEQUENCE
{
  realtimePower INTEGER(0..65535),
  chargingGunState BOOLEAN,
  fuelRangeElec INTEGER(0..65535),
  chargingType INTEGER(0..255),
  startTime INTEGER(0..2147483647) OPTIONAL,
  endTime INTEGER(0..2147483647) OPTIONAL,
  chargingPileID IA5String(SIZE(0..64)) OPTIONAL,
  chargingPileSupplier IA5String(SIZE(0..64)) OPTIONAL,
  workingCurrent INTEGER(0..65535) OPTIONAL,
  workingVoltage INTEGER(0..65535) OPTIONAL,
  mileageSinceLastCharge INTEGER(0..65535) OPTIONAL,
  powerUsageSinceLastCharge INTEGER(0..65535) OPTIONAL,
  mileageOfDay INTEGER(0..65535) OPTIONAL,
  powerUsageOfDay INTEGER(0..65535) OPTIONAL,
  staticEnergyConsumption INTEGER(0..65535) OPTIONAL,
  chargingElectricityPhase INTEGER(0..255) OPTIONAL,
  chargingDuration INTEGER(0..2147483647) OPTIONAL,
  lastChargeEndingPower INTEGER(0..65535) OPTIONAL,
  totalBatteryCapacity INTEGER(0..65535) OPTIONAL,
  fotaLowestVoltage INTEGER(0..255) OPTIONAL,
  mileage INTEGER(0..2147483647),
  extendedData1 INTEGER(0..2147483647) OPTIONAL,
  extendedData2 INTEGER(0..2147483647) OPTIONAL,
  extendedData3 IA5String(SIZE(0..1024)) OPTIONAL,
  extendedData4 IA5String(SIZE(0..1024)) OPTIONAL
}

END
