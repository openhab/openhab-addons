ApplicationDataModule

DEFINITIONS
AUTOMATIC TAGS ::= 
BEGIN
MP_UserLoggingInReq ::= SEQUENCE
{
  password IA5String(SIZE(6..30)),
  deviceId IA5String(SIZE(1..200)) OPTIONAL
}
MP_UserLoggingInResp ::= SEQUENCE
{
  token IA5String(SIZE(40)) OPTIONAL,
  refreshToken IA5String(SIZE(40)) OPTIONAL,
  tokenExpiration Timestamp OPTIONAL,
  vinList SEQUENCE SIZE(1..256) OF VinInfo OPTIONAL,
  userPhoto IA5String(SIZE(1..128)) OPTIONAL,
  userName IA5String(SIZE(8..12)),
  languageType LanguageType OPTIONAL
}
APPUpgradeInfoReq ::= SEQUENCE
{
  appType APPType,
  appVersion IA5String(SIZE(1..50))
}
APPUpgradeInfoResp ::= SEQUENCE
{
  hasNewVersion BOOLEAN,
  appVersion IA5String(SIZE(1..50)) OPTIONAL,
  forcedUpdate BOOLEAN OPTIONAL,
  updateUrl IA5String(SIZE(1..200)) OPTIONAL,
  updateInfoEn OCTET STRING(SIZE(1..500)) OPTIONAL,
  updateInfoTh OCTET STRING(SIZE(1..500)) OPTIONAL
}
MPAppAttributeResp ::= SEQUENCE
{
  dataAppAttribute IA5String(SIZE(1..65535)) OPTIONAL
}
AdvertiseResp ::= SEQUENCE
{
  advertiseVersion INTEGER(0..281474976710655) OPTIONAL,
  advertises SEQUENCE SIZE(0..255) OF Advertise OPTIONAL
}
MessageListReq ::= SEQUENCE
{
  startEndNumber StartEndNumber,
  messageGroup IA5String(SIZE(1..20)) OPTIONAL
}
MessageListResp ::= SEQUENCE
{
  recordsNumber INTEGER(0..281474976710655),
  messages SEQUENCE SIZE(1..256) OF Message OPTIONAL
}
GetUnreadMessageCountResp ::= SEQUENCE
{
  totalNumber INTEGER(0..281474976710655),
  newsNumber INTEGER(0..281474976710655),
  commandNumber INTEGER(0..281474976710655),
  alarmNumber INTEGER(0..281474976710655)
}
SetNotificationCountReq ::= SEQUENCE
{
  notificationCount INTEGER(0..255)
}
Timestamp ::= SEQUENCE
{
  seconds INTEGER(0..4294967295)
}
VinInfo ::= SEQUENCE
{
  vin IA5String(SIZE(17)),
  name OCTET STRING(SIZE(1..128)) OPTIONAL,
  series IA5String(SIZE(1..10)),
  brandName OCTET STRING(SIZE(1..24)),
  modelName OCTET STRING(SIZE(1..100)),
  vehiclePhoto IA5String(SIZE(1..128)) OPTIONAL,
  isAcivate BOOLEAN,
  isCurrentVehicle INTEGER(0..10) OPTIONAL,
  modelYear IA5String(SIZE(4)) OPTIONAL,
  colorName OCTET STRING(SIZE(1..50)) OPTIONAL,
  modelConfigurationJsonStr IA5String(SIZE(1..1024)) OPTIONAL,
  bindTime Timestamp OPTIONAL,
  tboxSimNo IA5String(SIZE(19)) OPTIONAL
}
LanguageType ::= ENUMERATED
{
  thai(0),
  english(1),
  china(2),
  de(3),
  fr(4),
  es(5),
  nl(6),
  nn(7),
  da(8),
  sv(9),
  it(10),
  pt(11),
  pl(12),
  el(13),
  fi(14),
  arabic(15),
  hindi(16)
}
APPType ::= ENUMERATED
{
  ios(0),
  android(1)
}
Advertise ::= SEQUENCE
{
  advertiseType IA5String(SIZE(3)) OPTIONAL,
  title OCTET STRING(SIZE(1..128)) OPTIONAL,
  photoUrl IA5String(SIZE(1..255)) OPTIONAL,
  detailsUrl IA5String(SIZE(1..255)) OPTIONAL,
  startTime Timestamp OPTIONAL,
  endTime Timestamp OPTIONAL
}
StartEndNumber ::= SEQUENCE
{
  startNumber INTEGER(0..281474976710655),
  endNumber INTEGER(0..281474976710655)
}
Message ::= SEQUENCE
{
  messageId INTEGER(0..281474976710655),
  messageType IA5String(SIZE(3)),
  title OCTET STRING(SIZE(1..128)),
  messageTime Timestamp,
  sender OCTET STRING(SIZE(1..64)),
  contentId SEQUENCE SIZE(1..256) OF ContentId OPTIONAL,
  content OCTET STRING(SIZE(1..2048)) OPTIONAL,
  readStatus INTEGER(-128..128) OPTIONAL,
  vin IA5String(SIZE(17)) OPTIONAL
}
Timestamp ::= SEQUENCE
{
  seconds INTEGER(0..4294967295)
}
ContentId ::= SEQUENCE
{
  contentId INTEGER(0..281474976710655),
  description OCTET STRING(SIZE(1..255)) OPTIONAL
}

END
