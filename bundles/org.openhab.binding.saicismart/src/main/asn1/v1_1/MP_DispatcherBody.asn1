MP_DispatcherBodyModule

DEFINITIONS
AUTOMATIC TAGS ::= 
BEGIN
MP_DispatcherBody ::= SEQUENCE
{
  uid IA5String(SIZE(50)) OPTIONAL,
  token IA5String(SIZE(40)) OPTIONAL,
  applicationID IA5String(SIZE(3)),
  vin IA5String(SIZE(17)) OPTIONAL,
  eventCreationTime INTEGER(0..4294967295),
  eventID INTEGER(0..281474976710655) OPTIONAL,
  messageID INTEGER(0..255),
  messageCounter MessageCounter OPTIONAL,
  ackRequired BOOLEAN OPTIONAL,
  statelessDispatcherMessage BOOLEAN OPTIONAL,
  crqmRequest BOOLEAN OPTIONAL,
  basicPosition BasicPosition OPTIONAL,
  networkInfo NetworkInfo OPTIONAL,
  simInfo NumericString(SIZE(19)) OPTIONAL,
  hmiLanguage LanguageType OPTIONAL,
  iccID NumericString(SIZE(20)),
  applicationDataLength INTEGER(0..4294967295),
  applicationDataEncoding DataEncodingType OPTIONAL,
  applicationDataProtocolVersion INTEGER(0..65535),
  testFlag INTEGER(1..3) OPTIONAL,
  result INTEGER(0..65535) OPTIONAL,
  errorMessage OCTET STRING(SIZE(1..1024)) OPTIONAL
}
MessageCounter ::= SEQUENCE
{
  uplinkCounter INTEGER(0..255),
  downlinkCounter INTEGER(0..255)
}
BasicPosition ::= SEQUENCE
{
  latitude INTEGER(-90000000..90000000),
  longitude INTEGER(-180000000..180000000)
}
NetworkInfo ::= SEQUENCE
{
  mccNetwork NumericString(SIZE(3)),
  mncNetwork NumericString(SIZE(3)),
  mccSim NumericString(SIZE(3)),
  mncSim NumericString(SIZE(3)),
  signalStrength INTEGER(0..99)
}
LanguageType ::= ENUMERATED
{
  simplifiedChinese(0),
  english(1),
  spanish(2),
  arabic(3),
  hindi(4)
}
DataEncodingType ::= ENUMERATED
{
  perUnaligned(0),
  der(1),
  ber(2)
}

END
