MP_DispatcherBodyModule

DEFINITIONS
AUTOMATIC TAGS ::= 
BEGIN
MP_DispatcherBody ::= SEQUENCE
{
  uid IA5String(SIZE(50)) OPTIONAL,
  token IA5String(SIZE(40)) OPTIONAL,
  applicationID IA5String(SIZE(3)),
  vin IA5String(SIZE(17)) OPTIONAL,
  messageID INTEGER(0..255),
  eventCreationTime INTEGER(0..2147483647),
  eventID INTEGER(0..2147483647) OPTIONAL,
  ulMessageCounter INTEGER(0..65535) OPTIONAL,
  dlMessageCounter INTEGER(0..65535) OPTIONAL,
  ackMessageCounter INTEGER(0..65535) OPTIONAL,
  ackRequired BOOLEAN OPTIONAL,
  applicationDataLength INTEGER(0..65535) OPTIONAL,
  applicationDataEncoding DataEncodingType OPTIONAL,
  applicationDataProtocolVersion INTEGER(0..65535) OPTIONAL,
  testFlag INTEGER(1..3) OPTIONAL,
  result INTEGER(0..65535) OPTIONAL,
  errorMessage OCTET STRING(SIZE(1..1024)) OPTIONAL
}
DataEncodingType ::= ENUMERATED
{
  perUnaligned(0),
  der(1),
  ber(2)
}

END
